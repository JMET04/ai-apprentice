; AI CAD Constraint Drawer 1.2.0
; Intentionally ASCII-only. UTF-8 is used only for user request/result files.
; Commands: AICAD_AI, AICAD_DRAW, AICAD_VALIDATE, AICAD_INFO, AICAD_SETUP, AICAD_DOCTOR

(vl-load-com)

(setq aicad:*layer* "AICAD_GEOMETRY")
(setq aicad:*regapp* "AICAD")
(setq aicad:*version* "1.2.0")

(defun aicad:split (text delimiter / position result)
  (setq result '())
  (while (setq position (vl-string-search delimiter text))
    (setq result (cons (substr text 1 position) result))
    (setq text (substr text (+ position (strlen delimiter) 1)))
  )
  (reverse (cons text result))
)

(defun aicad:point-close-p (a b tolerance)
  (<= (distance (list (car a) (cadr a) 0.0) (list (car b) (cadr b) 0.0)) tolerance)
)

(defun aicad:known-point-p (point points tolerance / found)
  (setq found nil)
  (while (and points (not found))
    (if (aicad:point-close-p point (car points) tolerance) (setq found T))
    (setq points (cdr points))
  )
  found
)

(defun aicad:number (text / value)
  (setq value (distof text 2))
  (if (and value (<= (abs value) 1000000000.0)) value nil)
)

(defun aicad:id-valid-p (text / index code valid)
  (setq index 1 valid (> (strlen text) 0))
  (while (and valid (<= index (strlen text)))
    (setq code (ascii (substr text index 1)))
    (if (not (or (and (>= code 48) (<= code 57))
                 (and (>= code 65) (<= code 90))
                 (and (>= code 97) (<= code 122)) (= code 95)))
      (setq valid nil)
    )
    (setq index (1+ index))
  )
  valid
)

(defun aicad:parse-point4 (parts first / a b c d)
  (setq a (aicad:number (nth first parts)) b (aicad:number (nth (1+ first) parts))
        c (aicad:number (nth (+ first 2) parts)) d (aicad:number (nth (+ first 3) parts)))
  (if (and a b c d) (list (list a b) (list c d)) nil)
)

(defun aicad:parse-record (parts version / kind id values cx cy radius start-angle end-angle proof)
  (setq kind (car parts) id (nth 1 parts))
  (cond
    ((and (= kind "LINE") (>= (length parts) (if (= version "2") 12 8)) (aicad:id-valid-p id)
          (setq values (aicad:parse-point4 parts 2)))
      (if (= version "2")
        (setq proof (aicad:parse-point4 parts 8))
        (setq proof nil))
      (if (or (/= version "2") proof)
        (list "LINE" id (car values) (cadr values) (if proof (car proof) nil) (if proof (cadr proof) nil)) nil))
    ((and (= version "2") (= kind "CIRCLE") (>= (length parts) 11) (aicad:id-valid-p id)
          (setq cx (aicad:number (nth 2 parts))) (setq cy (aicad:number (nth 3 parts)))
          (setq radius (aicad:number (nth 4 parts))) (> radius 0.0)
          (setq proof (aicad:parse-point4 parts 7)))
      (list "CIRCLE" id (list cx cy) radius (car proof) (cadr proof)))
    ((and (= version "2") (= kind "ARC") (>= (length parts) 13) (aicad:id-valid-p id)
          (setq cx (aicad:number (nth 2 parts))) (setq cy (aicad:number (nth 3 parts)))
          (setq radius (aicad:number (nth 4 parts))) (> radius 0.0)
          (setq start-angle (aicad:number (nth 5 parts))) (setq end-angle (aicad:number (nth 6 parts)))
          (not (equal (rem (- end-angle start-angle) 360.0) 0.0 0.000000001))
          (setq proof (aicad:parse-point4 parts 9)))
      (list "ARC" id (list cx cy) radius start-angle end-angle
            (car proof) (cadr proof)))
    (T nil)
  )
)

(defun aicad:anchor (record) (nth 2 record))

(defun aicad:proof-base (record)
  (cond ((= (car record) "LINE") (nth 4 record))
        ((= (car record) "CIRCLE") (nth 4 record))
        ((= (car record) "ARC") (nth 6 record)))
)

(defun aicad:proof-offset (record)
  (cond ((= (car record) "LINE") (nth 5 record))
        ((= (car record) "CIRCLE") (nth 5 record))
        ((= (car record) "ARC") (nth 7 record)))
)

(defun aicad:proof-valid-p (record known-points tolerance / base offset expected)
  (setq base (aicad:proof-base record) offset (aicad:proof-offset record))
  (and base offset (aicad:known-point-p base known-points tolerance)
       (setq expected (list (+ (car base) (car offset)) (+ (cadr base) (cadr offset))))
       (aicad:point-close-p expected (aicad:anchor record) tolerance))
)

(defun aicad:arc-point (center radius angle / radians)
  (setq radians (* angle (/ pi 180.0)))
  (list (+ (car center) (* radius (cos radians))) (+ (cadr center) (* radius (sin radians))))
)

(defun aicad:record-points (record / kind center radius)
  (setq kind (car record))
  (cond
    ((= kind "LINE")
      (list (nth 2 record) (nth 3 record)
            (list (/ (+ (car (nth 2 record)) (car (nth 3 record))) 2.0)
                  (/ (+ (cadr (nth 2 record)) (cadr (nth 3 record))) 2.0))))
    ((= kind "CIRCLE") (list (nth 2 record)))
    ((= kind "ARC")
      (setq center (nth 2 record) radius (nth 3 record))
      (list center (aicad:arc-point center radius (nth 4 record))
                   (aicad:arc-point center radius (nth 5 record))))
  )
)

(defun aicad:duplicate-p (candidate records tolerance / found current kind)
  (setq found nil kind (car candidate))
  (while (and records (not found))
    (setq current (car records))
    (if (= kind (car current))
      (cond
        ((= kind "LINE")
          (if (or (and (aicad:point-close-p (nth 2 candidate) (nth 2 current) tolerance)
                       (aicad:point-close-p (nth 3 candidate) (nth 3 current) tolerance))
                  (and (aicad:point-close-p (nth 2 candidate) (nth 3 current) tolerance)
                       (aicad:point-close-p (nth 3 candidate) (nth 2 current) tolerance))) (setq found T)))
        ((= kind "CIRCLE")
          (if (and (aicad:point-close-p (nth 2 candidate) (nth 2 current) tolerance)
                   (equal (nth 3 candidate) (nth 3 current) tolerance)) (setq found T)))
        ((= kind "ARC")
          (if (and (aicad:point-close-p (nth 2 candidate) (nth 2 current) tolerance)
                   (equal (nth 3 candidate) (nth 3 current) tolerance)
                   (equal (nth 4 candidate) (nth 4 current) tolerance)
                   (equal (nth 5 candidate) (nth 5 current) tolerance)) (setq found T)))
      )
    )
    (setq records (cdr records))
  )
  found
)

(defun aicad:read-plan (filename / stream raw header fields version tolerance source-hash records known-points
                                  parsed end-parts expected-count line-number error-message points)
  (setq stream (open filename "r") records '() known-points (list (list 0.0 0.0)) line-number 0 error-message nil)
  (if (not stream)
    (list nil "Cannot open plan file.")
    (progn
      (setq header (read-line stream) line-number 1)
      (if header (setq fields (aicad:split header "|")))
      (if (not (and fields (>= (length fields) 5) (= (nth 0 fields) "AICAD")
                    (or (= (nth 1 fields) "1") (= (nth 1 fields) "2"))))
        (setq error-message "Invalid AICAD header or unsupported version.")
        (progn
          (setq version (nth 1 fields) tolerance (aicad:number (nth 3 fields)) source-hash (nth 4 fields))
          (if (not (and tolerance (> tolerance 0.0) (<= tolerance 0.1))) (setq error-message "Invalid tolerance in header."))
        )
      )
      (while (and (not error-message) (not end-parts) (setq raw (read-line stream)))
        (setq line-number (1+ line-number) fields (aicad:split raw "|"))
        (cond
          ((= (car fields) "END")
            (setq end-parts fields)
            (if (read-line stream) (setq error-message "Unexpected content after END record.")))
          ((not (setq parsed (aicad:parse-record fields version)))
            (setq error-message (strcat "Invalid entity record at file line " (itoa line-number) ".")))
          ((and (= (car parsed) "LINE") (aicad:point-close-p (nth 2 parsed) (nth 3 parsed) tolerance))
            (setq error-message (strcat "Zero-length entity " (nth 1 parsed) ".")))
          ((and (= version "1") records (not (aicad:known-point-p (aicad:anchor parsed) known-points tolerance)))
            (setq error-message (strcat "Disconnected start point on " (nth 1 parsed) ".")))
          ((and (= version "2") (not (aicad:proof-valid-p parsed known-points tolerance)))
            (setq error-message (strcat "Invalid mathematical anchor proof on " (nth 1 parsed) ".")))
          ((aicad:duplicate-p parsed records tolerance)
            (setq error-message (strcat "Duplicate geometry on " (nth 1 parsed) ".")))
          (T
            (setq records (append records (list parsed)) points (aicad:record-points parsed))
            (foreach point points (setq known-points (cons point known-points))))
        )
      )
      (close stream)
      (if (and (not error-message) (not end-parts)) (setq error-message "Missing END record."))
      (if (and (not error-message) (not records)) (setq error-message "Plan contains no entities."))
      (if (and (not error-message) records (not (aicad:point-close-p (aicad:anchor (car records)) (list 0.0 0.0) tolerance)))
        (setq error-message "The first entity anchor is not origin (0,0)."))
      (if (and (not error-message) end-parts (< (length end-parts) 3)) (setq error-message "Invalid END record."))
      (if (and (not error-message) end-parts)
        (progn
          (setq expected-count (atoi (nth 1 end-parts)))
          (if (/= expected-count (length records)) (setq error-message "END record count does not match entities."))
          (if (/= (nth 2 end-parts) source-hash) (setq error-message "Plan hash markers do not match."))))
      (if error-message (list nil error-message) (list records nil))
    )
  )
)

(defun aicad:ensure-layer ()
  (if (not (tblsearch "LAYER" aicad:*layer*))
    (entmake (list '(0 . "LAYER") '(100 . "AcDbSymbolTableRecord") '(100 . "AcDbLayerTableRecord")
                   (cons 2 aicad:*layer*) '(70 . 0) '(62 . 7) '(6 . "Continuous"))))
  (regapp aicad:*regapp*)
)

(defun aicad:xdata (record index)
  (list -3 (list aicad:*regapp* (cons 1000 (nth 1 record)) (cons 1000 (car record)) (cons 1070 index)))
)

(defun aicad:create-entity (record index / kind center)
  (setq kind (car record))
  (cond
    ((= kind "LINE")
      (entmakex (list '(0 . "LINE") '(100 . "AcDbEntity") (cons 8 aicad:*layer*) '(100 . "AcDbLine")
                      (cons 10 (append (nth 2 record) (list 0.0))) (cons 11 (append (nth 3 record) (list 0.0)))
                      (aicad:xdata record index))))
    ((= kind "CIRCLE")
      (entmakex (list '(0 . "CIRCLE") '(100 . "AcDbEntity") (cons 8 aicad:*layer*) '(100 . "AcDbCircle")
                      (cons 10 (append (nth 2 record) (list 0.0))) (cons 40 (nth 3 record))
                      (aicad:xdata record index))))
    ((= kind "ARC")
      (entmakex (list '(0 . "ARC") '(100 . "AcDbEntity") (cons 8 aicad:*layer*) '(100 . "AcDbCircle")
                      (cons 10 (append (nth 2 record) (list 0.0))) (cons 40 (nth 3 record)) '(100 . "AcDbArc")
                      (cons 50 (* (nth 4 record) (/ pi 180.0))) (cons 51 (* (nth 5 record) (/ pi 180.0)))
                      (aicad:xdata record index))))
  )
)

(defun aicad:choose-plan () (getfiled "Select compiled AI CAD plan" "" "aicad" 0))
(defun aicad:validate-file (filename) (aicad:read-plan filename))

(defun aicad:draw-file (filename / result records created entity index failure)
  (setq result (aicad:read-plan filename))
  (if (not (car result))
    (list nil (cadr result))
    (progn
      (setq records (car result) created '() index 1 failure nil)
      (aicad:ensure-layer)
      (while (and records (not failure))
        (setq entity (aicad:create-entity (car records) index))
        (if entity
          (setq created (cons entity created) records (cdr records) index (1+ index))
          (setq failure T)))
      (if failure
        (progn (foreach entity created (if (entget entity) (entdel entity))) (list nil "Entity creation failed; batch rolled back."))
        (list T (length created) (reverse created)))
    )
  )
)

(defun aicad:quote (text) (strcat "\"" text "\""))

(defun aicad:runtime-ready-p ()
  (and (getenv "AICAD_PYTHON") (findfile (getenv "AICAD_PYTHON"))
       (getenv "AICAD_RUNNER") (findfile (getenv "AICAD_RUNNER"))
       (getenv "AICAD_JOBS") (vl-file-directory-p (getenv "AICAD_JOBS")))
)

(defun aicad:run (arguments visible wait / shell command result executable)
  (setq executable (if (and visible (getenv "AICAD_PYTHONW") (findfile (getenv "AICAD_PYTHONW")))
                     (getenv "AICAD_PYTHONW") (getenv "AICAD_PYTHON")))
  (setq command (strcat (aicad:quote executable) " " (aicad:quote (getenv "AICAD_RUNNER")) " " arguments)
        shell (vlax-create-object "WScript.Shell")
        result (vlax-invoke-method shell 'Run command (if visible 1 0) (if wait :vlax-true :vlax-false)))
  (vlax-release-object shell)
  result
)

(defun aicad:job-directory (/ root stamp directory)
  (setq root (getenv "AICAD_JOBS") stamp (vl-string-translate "." "_" (rtos (getvar "CDATE") 2 8))
        directory (strcat root "\\" stamp))
  (if (vl-mkdir directory) directory (if (vl-file-directory-p directory) directory nil))
)

(defun aicad:read-result (filename / stream status message provider count)
  (if (setq stream (open filename "r" "utf8"))
    (progn
      (setq status (read-line stream) message (read-line stream) provider (read-line stream) count (read-line stream))
      (close stream)
      (list status message provider count))
    nil)
)

(defun c:AICAD_AI (/ request job request-file result-file stream arguments exit-code result draw-result)
  (cond
    ((not (aicad:runtime-ready-p)) (princ "\nAICAD runtime is not ready. Re-run install.ps1, restart AutoCAD, then run AICAD_DOCTOR."))
    ((not (setq request (getstring T "\nDescribe the 2D part (dimensions required): "))) (princ "\nCancelled."))
    ((= (vl-string-trim " " request) "") (princ "\nRequest is empty."))
    ((not (setq job (aicad:job-directory))) (princ "\nCannot create AICAD job directory."))
    (T
      (setq request-file (strcat job "\\request.txt") result-file (strcat job "\\result.txt"))
      (if (setq stream (open request-file "w" "utf8"))
        (progn
          (write-line request stream) (close stream)
          (setq arguments (strcat "natural " (aicad:quote request-file) " --out " (aicad:quote job)
                                  " --name drawing --result " (aicad:quote result-file)))
          (princ "\nResolving constraints and validating geometry...")
          (setq exit-code (aicad:run arguments nil T) result (aicad:read-result result-file))
          (if (and (= exit-code 0) result (= (car result) "OK"))
            (progn
              (setq draw-result (aicad:draw-file (cadr result)))
              (if (car draw-result)
                (princ (strcat "\nAICAD drew " (itoa (cadr draw-result)) " validated entities using " (nth 2 result) ". One UNDO reverts the batch."))
                (princ (strcat "\nAICAD rejected generated geometry: " (cadr draw-result)))))
            (princ (strcat "\nAICAD generation failed: " (if result (cadr result) "No result file was produced."))))
        )
        (princ "\nCannot write the UTF-8 request file.")))
  )
  (princ)
)

(defun c:AICAD_VALIDATE (/ filename result)
  (if (setq filename (aicad:choose-plan))
    (progn (setq result (aicad:validate-file filename))
      (if (car result)
        (princ (strcat "\nAICAD valid: " (itoa (length (car result))) " entities; origin and anchor proofs verified."))
        (princ (strcat "\nAICAD invalid: " (cadr result))))))
  (princ)
)

(defun c:AICAD_DRAW (/ filename result)
  (if (setq filename (aicad:choose-plan))
    (progn (setq result (aicad:draw-file filename))
      (if (not (car result))
        (princ (strcat "\nAICAD rejected: " (cadr result)))
        (princ (strcat "\nAICAD drew " (itoa (cadr result)) " validated entities. One UNDO reverts the batch.")))))
  (princ)
)

(defun c:AICAD_INFO (/ selected data xdata payload strings)
  (if (setq selected (entsel "\nSelect an AICAD entity: "))
    (progn (setq data (entget (car selected) (list aicad:*regapp*)) xdata (assoc -3 data))
      (if xdata
        (progn (setq payload (cdr (cadr xdata)) strings (vl-remove-if-not '(lambda (item) (= (car item) 1000)) payload))
          (princ (strcat "\nAICAD ID: " (cdr (nth 0 strings)) "; type: " (if (nth 1 strings) (cdr (nth 1 strings)) "LINE")
                         "; step: " (itoa (cdr (assoc 1070 payload))))))
        (princ "\nThe selected entity has no AICAD metadata."))))
  (princ)
)

(defun c:AICAD_SETUP ()
  (if (aicad:runtime-ready-p)
    (progn (aicad:run "setup-gui" T nil) (princ "\nProvider setup window opened."))
    (princ "\nAICAD runtime is not ready. Re-run install.ps1 and restart AutoCAD."))
  (princ)
)

(defun c:AICAD_DOCTOR (/ code)
  (if (aicad:runtime-ready-p)
    (progn (setq code (aicad:run "doctor" T T))
           (princ (strcat "\nAICAD runtime check completed with exit code " (itoa code) ".")))
    (princ "\nAICAD runtime FAILED: Python, runner, or job directory is missing. Re-run install.ps1."))
  (princ)
)

(princ (strcat "\nAI CAD Constraint Drawer " aicad:*version* " loaded. Commands: AICAD_AI, AICAD_DRAW, AICAD_VALIDATE, AICAD_INFO, AICAD_SETUP, AICAD_DOCTOR"))
(princ)
