(vl-load-com)

(defun aiapp:json-escape (value / result code)
  (setq result "")
  (foreach code (vl-string->list (if value value ""))
    (setq result
      (strcat result
        (cond
          ((= code 34) "\\\"")
          ((= code 92) "\\\\")
          ((= code 10) "\\n")
          ((= code 13) "\\r")
          ((= code 9) "\\t")
          (T (chr code))))))
  result)

(defun aiapp:json-string (value)
  (strcat "\"" (aiapp:json-escape value) "\""))

(defun aiapp:json-number (value)
  (if (numberp value) (rtos value 2 12) "null"))

(defun aiapp:json-point (value)
  (if (and (listp value) (>= (length value) 2))
    (strcat "[" (aiapp:json-number (nth 0 value)) "," (aiapp:json-number (nth 1 value)) ","
            (aiapp:json-number (if (nth 2 value) (nth 2 value) 0.0)) "]")
    "null"))

(defun aiapp:aicad-id (data / xdata app item found)
  (setq xdata (assoc -3 data) found nil)
  (if xdata
    (foreach app (cdr xdata)
      (foreach item (cdr app)
        (if (and (not found) (= (car item) 1000)) (setq found (cdr item))))))
  found)

(defun aiapp:inbox-path (/ configured fallback)
  (setq configured (getenv "AI_APPRENTICE_NATIVE_SELECTION_INBOX"))
  (if (and configured (/= configured ""))
    configured
    (progn
      (setq fallback (strcat (getvar "DWGPREFIX") ".transparent-apprentice\\native-selections\\inbox"))
      (vl-mkdir (strcat (getvar "DWGPREFIX") ".transparent-apprentice"))
      (vl-mkdir (strcat (getvar "DWGPREFIX") ".transparent-apprentice\\native-selections"))
      (vl-mkdir fallback)
      fallback)))

(defun aiapp:launch-companion (/ root script arguments)
  (setq root (getenv "AI_APPRENTICE_PLUGIN_ROOT"))
  (if (and root (/= root ""))
    (progn
      (setq script (strcat root "\\assets\\desktop-companion\\AI-Apprentice-Companion.ps1"))
      (setq arguments
        (strcat "-NoProfile -ExecutionPolicy Bypass -WindowStyle Hidden -File \"" script
                "\" -InboxPath \"" (aiapp:inbox-path) "\""))
      (startapp "powershell.exe" arguments))))

(defun aiapp:write-selection (ename pick-point trigger / data handle kind layer layout aicad-id object-id
                              start-point end-point center radius angle-start angle-end file stream stamp path)
  (setq data (entget ename '("*")))
  (setq handle (cdr (assoc 5 data)))
  (setq kind (cdr (assoc 0 data)))
  (setq layer (cdr (assoc 8 data)))
  (setq layout (cdr (assoc 410 data)))
  (setq aicad-id (aiapp:aicad-id data))
  (setq object-id (if aicad-id aicad-id (strcat "HANDLE:" handle)))
  (setq start-point (cdr (assoc 10 data)))
  (setq end-point (cdr (assoc 11 data)))
  (setq center (cdr (assoc 10 data)))
  (setq radius (cdr (assoc 40 data)))
  (setq angle-start (cdr (assoc 50 data)))
  (setq angle-end (cdr (assoc 51 data)))
  (setq stamp (rtos (* 86400000.0 (getvar "CDATE")) 2 0))
  (setq path (strcat (aiapp:inbox-path) "\\selection-aicad-" stamp "-" handle ".json"))
  (setq stream (open path "w" "utf8"))
  (if stream
    (progn
      (write-line "{" stream)
      (write-line "  \"format\": \"ai_apprentice_native_selection_v1\"," stream)
      (write-line "  \"surfaceKind\": \"engineering_native_object\"," stream)
      (write-line "  \"host\": {" stream)
      (write-line "    \"application\": \"AICAD / AutoCAD\"," stream)
      (write-line (strcat "    \"version\": " (aiapp:json-string (getvar "ACADVER")) ",") stream)
      (write-line (strcat "    \"documentName\": " (aiapp:json-string (getvar "DWGNAME")) ",") stream)
      (write-line (strcat "    \"documentPath\": " (aiapp:json-string (strcat (getvar "DWGPREFIX") (getvar "DWGNAME"))) ",") stream)
      (write-line (strcat "    \"sessionId\": " (aiapp:json-string (strcat "autocad-" (getvar "DWGNAME")))) stream)
      (write-line "  }," stream)
      (write-line "  \"selection\": {" stream)
      (write-line "    \"nativeKind\": \"autocad_entity_or_subentity\"," stream)
      (write-line (strcat "    \"nativeLocator\": " (aiapp:json-string (strcat "handle:" handle "/pick:" (aiapp:json-point pick-point))) ",") stream)
      (write-line (strcat "    \"objectId\": " (aiapp:json-string object-id) ",") stream)
      (write-line (strcat "    \"objectType\": " (aiapp:json-string kind) ",") stream)
      (write-line "    \"properties\": {" stream)
      (write-line (strcat "      \"handle\": " (aiapp:json-string handle) ",") stream)
      (write-line (strcat "      \"layer\": " (aiapp:json-string layer) ",") stream)
      (write-line (strcat "      \"layout\": " (aiapp:json-string layout) ",") stream)
      (write-line (strcat "      \"pickPoint\": " (aiapp:json-point pick-point) ",") stream)
      (write-line (strcat "      \"startPoint\": " (aiapp:json-point start-point) ",") stream)
      (write-line (strcat "      \"endPoint\": " (aiapp:json-point end-point) ",") stream)
      (write-line (strcat "      \"center\": " (aiapp:json-point center) ",") stream)
      (write-line (strcat "      \"radius\": " (aiapp:json-number radius) ",") stream)
      (write-line (strcat "      \"startAngle\": " (aiapp:json-number angle-start) ",") stream)
      (write-line (strcat "      \"endAngle\": " (aiapp:json-number angle-end)) stream)
      (write-line "    }," stream)
      (write-line (strcat "    \"relationships\": [" (aiapp:json-string (strcat "drawing-handle:" handle)) "," (aiapp:json-string (strcat "layer:" layer)) "],") stream)
      (write-line "    \"protectedObjectIds\": []" stream)
      (write-line "  }," stream)
      (write-line "  \"capture\": {" stream)
      (write-line (strcat "    \"trigger\": " (aiapp:json-string trigger) ",") stream)
      (write-line "    \"adapter\": \"aicad_autocad_xdata_selection_bridge_v1\"" stream)
      (write-line "  }," stream)
      (write-line "  \"interactionPreference\": {\"backgroundPreparation\": true, \"allowScreenControl\": false, \"keepHostDocumentOpen\": true}," stream)
      (write-line "  \"executionBoundary\": {\"mode\": \"host_agent_plugin\", \"reasoningOwner\": \"host_agent\", \"modelApiRequired\": false, \"apiKeyRequired\": false, \"companionRole\": \"capture_and_handoff_only\"}," stream)
      (write-line "  \"reviewOnly\": true," stream)
      (write-line "  \"accepted\": false," stream)
      (write-line "  \"ruleEnabled\": false," stream)
      (write-line "  \"packagingGated\": true" stream)
      (write-line "}" stream)
      (close stream)
      (aiapp:launch-companion)
      (princ (strcat "\nAI Apprentice captured " kind " " object-id " for agent review."))
      path)
    (progn (princ "\nAI Apprentice could not write the native selection file.") nil)))

(defun aiapp:selected-or-picked (pick-point / implied nested)
  (setq implied (ssget "_I"))
  (cond
    ((and implied (= (sslength implied) 1)) (ssname implied 0))
    ((setq nested (nentselp nil pick-point)) (car nested))
    (T nil)))

(defun aiapp:right-click (reactor parameters / pick-point ename)
  (setq pick-point (car parameters))
  (if (setq ename (aiapp:selected-or-picked pick-point))
    (aiapp:write-selection ename pick-point "right_click")))

(defun c:AIAPPRENTICE_EDIT (/ picked)
  (if (setq picked (nentsel "\nSelect a line, face, dimension, or AICAD object for AI Apprentice: "))
    (aiapp:write-selection (car picked) (cadr picked) "command"))
  (princ))

(defun c:AIAPPRENTICE_RIGHTCLICK_ON ()
  (if (and (boundp 'aiapp:*mouse-reactor*) aiapp:*mouse-reactor*)
    (vlr-remove aiapp:*mouse-reactor*))
  (setq aiapp:*mouse-reactor* (vlr-mouse-reactor "AI Apprentice native selection" '((:vlr-beginRightClick . aiapp:right-click))))
  (vlr-set-notification aiapp:*mouse-reactor* 'active-document-only)
  (princ "\nAI Apprentice right-click native selection bridge is ON.")
  (princ))

(defun c:AIAPPRENTICE_RIGHTCLICK_OFF ()
  (if (and (boundp 'aiapp:*mouse-reactor*) aiapp:*mouse-reactor*)
    (progn (vlr-remove aiapp:*mouse-reactor*) (setq aiapp:*mouse-reactor* nil)))
  (princ "\nAI Apprentice right-click native selection bridge is OFF.")
  (princ))

(c:AIAPPRENTICE_RIGHTCLICK_ON)
(princ "\nAI Apprentice native object bridge loaded. Commands: AIAPPRENTICE_EDIT, AIAPPRENTICE_RIGHTCLICK_ON, AIAPPRENTICE_RIGHTCLICK_OFF")
(princ)
