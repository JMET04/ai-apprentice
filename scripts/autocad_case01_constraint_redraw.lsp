; AutoCAD host harness for the case 01 FEFCO 0201 constraint redraw.
(vl-load-com)

(defun case01:emit (stream text)
  (write-line text stream)
  (princ (strcat "\n" text))
)

(defun case01:count-lines (layer / selection)
  (setq selection (ssget "_X" (list '(0 . "LINE") (cons 8 layer))))
  (if selection (sslength selection) 0)
)

(defun case01:count-entities (layer / selection)
  (setq selection (ssget "_X" (list (cons 8 layer))))
  (if selection (sslength selection) 0)
)

(defun case01:count-aicad-xdata (layers / selection index data layer count)
  (setq selection (ssget "_X" '((0 . "LINE"))) index 0 count 0)
  (if selection
    (while (< index (sslength selection))
      (setq data (entget (ssname selection index) '("AICAD"))
            layer (cdr (assoc 8 data)))
      (if (and (member layer layers) (assoc -3 data))
        (setq count (1+ count)))
      (setq index (1+ index))
    )
  )
  count
)

(defun case01:companion-ok-p ()
  (and (> (case01:count-entities "GLUE") 0)
       (> (case01:count-entities "DIMENSION") 0)
       (> (case01:count-entities "TEXT") 0))
)

(defun case01:erase-layer (layer / selection)
  (setq selection (ssget "_X" (list (cons 8 layer))))
  (if selection (command "_.ERASE" selection ""))
)

(defun case01:move-layer (layer dx dy / selection index entity data start end offset)
  (setq selection (ssget "_X" (list '(0 . "LINE") (cons 8 layer)))
        index 0
        offset (list dx dy 0.0))
  (if selection
    (while (< index (sslength selection))
      (setq entity (ssname selection index)
            data (entget entity '("AICAD"))
            start (cdr (assoc 10 data))
            end (cdr (assoc 11 data)))
      (setq data (subst (cons 10 (mapcar '+ start offset)) (assoc 10 data) data))
      (setq data (subst (cons 11 (mapcar '+ end offset)) (assoc 11 data) data))
      (entmod data)
      (entupd entity)
      (setq index (1+ index))
    )
  )
)

(defun case01:make-layer (name color /)
  (if (not (tblsearch "LAYER" name))
    (entmake
      (list
        '(0 . "LAYER")
        '(100 . "AcDbSymbolTableRecord")
        '(100 . "AcDbLayerTableRecord")
        (cons 2 name)
        '(70 . 0)
        (cons 62 color)
        '(6 . "Continuous")
      )
    )
  )
)

(defun case01:bounds (layers / selection index data layer start end xs ys)
  (setq selection (ssget "_X" '((0 . "LINE"))) index 0 xs '() ys '())
  (if selection
    (while (< index (sslength selection))
      (setq data (entget (ssname selection index))
            layer (cdr (assoc 8 data)))
      (if (member layer layers)
        (progn
          (setq start (cdr (assoc 10 data)) end (cdr (assoc 11 data)))
          (setq xs (cons (car start) (cons (car end) xs))
                ys (cons (cadr start) (cons (cadr end) ys)))
        )
      )
      (setq index (1+ index))
    )
  )
  (if xs
    (list (apply 'min xs) (apply 'min ys) (apply 'max xs) (apply 'max ys))
    nil
  )
)

(defun case01:bounds-ok-p (bounds / tolerance)
  (setq tolerance 0.000001)
  (and bounds
       (equal (nth 0 bounds) 0.0 tolerance)
       (equal (nth 1 bounds) 0.0 tolerance)
       (equal (nth 2 bounds) 1575.0 tolerance)
       (equal (nth 3 bounds) 597.0 tolerance))
)

(defun case01:draw (/ root plugin cut crease slot target report stream result ok bounds)
  (setq root (vl-string-translate "\\" "/" (getenv "AICAD_CASE_ROOT"))
        plugin (strcat root "/AiCadConstraint.lsp")
        cut (strcat root "/case01_fefco0201_cut.aicad")
        crease (strcat root "/case01_fefco0201_crease.aicad")
        slot (strcat root "/case01_fefco0201_slot.aicad")
        target (strcat root "/case01_fefco0201_constraint_redraw.dwg")
        report (strcat root "/draw-report.txt")
        stream (open report "w")
        ok T)
  (setvar "FILEDIA" 0)
  (setvar "CMDDIA" 0)
  (case01:emit stream "CASE01_DRAW_BEGIN")
  (foreach layer '("CUT" "CREASE" "SLOT" "AICAD_GEOMETRY") (case01:erase-layer layer))
  (case01:make-layer "CUT" 1)
  (case01:make-layer "CREASE" 5)
  (case01:make-layer "SLOT" 6)
  (if (not (load plugin nil))
    (progn (case01:emit stream "FAIL:PLUGIN_LOAD") (setq ok nil))
    (case01:emit stream "PASS:PLUGIN_LOAD"))
  (if ok
    (progn
      (setq aicad:*layer* "CUT" result (aicad:draw-file cut))
      (if (not (and (car result) (= (cadr result) 21)))
        (progn (case01:emit stream "FAIL:CUT_DRAW") (setq ok nil))
        (case01:emit stream "PASS:CUT_COUNT=21"))
      (setq aicad:*layer* "CREASE" result (aicad:draw-file crease))
      (if (not (and (car result) (= (cadr result) 12)))
        (progn (case01:emit stream "FAIL:CREASE_DRAW") (setq ok nil))
        (case01:emit stream "PASS:CREASE_COUNT=12"))
      (setq aicad:*layer* "SLOT" result (aicad:draw-file slot))
      (if (not (and (car result) (= (cadr result) 8)))
        (progn (case01:emit stream "FAIL:SLOT_DRAW") (setq ok nil))
        (case01:emit stream "PASS:SLOT_COUNT=8"))))
  (foreach layer '("CUT" "CREASE" "SLOT") (case01:move-layer layer 35.0 167.5))
  (case01:emit stream "PASS:CATALOG_DATUM_TRANSLATION=35,167.5")
  (if (not (and (= (case01:count-lines "CUT") 21)
                (= (case01:count-lines "CREASE") 12)
                (= (case01:count-lines "SLOT") 8)))
    (progn (case01:emit stream "FAIL:HOST_LAYER_COUNTS") (setq ok nil))
    (case01:emit stream "PASS:HOST_LAYER_COUNTS=21,12,8"))
  (if (/= (case01:count-aicad-xdata '("CUT" "CREASE" "SLOT")) 41)
    (progn (case01:emit stream "FAIL:HOST_AICAD_XDATA") (setq ok nil))
    (case01:emit stream "PASS:HOST_AICAD_XDATA=41"))
  (if (not (case01:companion-ok-p))
    (progn (case01:emit stream "FAIL:COMPANION_LAYERS") (setq ok nil))
    (case01:emit stream
      (strcat "PASS:COMPANION_LAYER_COUNTS="
              (itoa (case01:count-entities "GLUE")) ","
              (itoa (case01:count-entities "DIMENSION")) ","
              (itoa (case01:count-entities "TEXT")))))
  (setq bounds (case01:bounds '("CUT" "CREASE" "SLOT")))
  (if (not (case01:bounds-ok-p bounds))
    (progn (case01:emit stream "FAIL:HOST_BOUNDS") (setq ok nil))
    (case01:emit stream "PASS:HOST_BOUNDS=0,0,1575,597"))
  (if ok
    (progn
      (command "_.SAVEAS" "2018" target)
      (if (findfile target)
        (case01:emit stream "PASS:DWG_SAVE")
        (progn (case01:emit stream "FAIL:DWG_SAVE") (setq ok nil)))))
  (case01:emit stream (if ok "CASE01_DRAW_PASS" "CASE01_DRAW_FAIL"))
  (close stream)
  ok
)

(defun case01:verify (/ root report stream ok bounds)
  (setq root (vl-string-translate "\\" "/" (getenv "AICAD_CASE_ROOT"))
        report (strcat root "/verify-report.txt")
        stream (open report "w")
        ok T)
  (case01:emit stream "CASE01_VERIFY_BEGIN")
  (if (not (and (= (case01:count-lines "CUT") 21)
                (= (case01:count-lines "CREASE") 12)
                (= (case01:count-lines "SLOT") 8)))
    (progn (case01:emit stream "FAIL:PERSISTED_LAYER_COUNTS") (setq ok nil))
    (case01:emit stream "PASS:PERSISTED_LAYER_COUNTS=21,12,8"))
  (if (/= (case01:count-aicad-xdata '("CUT" "CREASE" "SLOT")) 41)
    (progn (case01:emit stream "FAIL:PERSISTED_AICAD_XDATA") (setq ok nil))
    (case01:emit stream "PASS:PERSISTED_AICAD_XDATA=41"))
  (if (not (case01:companion-ok-p))
    (progn (case01:emit stream "FAIL:PERSISTED_COMPANION_LAYERS") (setq ok nil))
    (case01:emit stream
      (strcat "PASS:PERSISTED_COMPANION_LAYER_COUNTS="
              (itoa (case01:count-entities "GLUE")) ","
              (itoa (case01:count-entities "DIMENSION")) ","
              (itoa (case01:count-entities "TEXT")))))
  (setq bounds (case01:bounds '("CUT" "CREASE" "SLOT")))
  (if (not (case01:bounds-ok-p bounds))
    (progn (case01:emit stream "FAIL:PERSISTED_BOUNDS") (setq ok nil))
    (case01:emit stream "PASS:PERSISTED_BOUNDS=0,0,1575,597"))
  (case01:emit stream (if ok "CASE01_VERIFY_PASS" "CASE01_VERIFY_FAIL"))
  (close stream)
  ok
)
